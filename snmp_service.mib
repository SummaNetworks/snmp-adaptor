-- This MIB Generated by the JBoss MIB Generator

JBOSS-AS-MIB DEFINITIONS ::=BEGIN

IMPORTS
	OBJECT-TYPE,
	NOTIFICATION-TYPE,
	Counter32,
	Gauge32,
	Counter64,
	TimeTicks
		FROM SNMPv2-SMI
	DisplayString,
	TruthValue
		FROM SNMPv2-TC;

jbossAsObjects		OBJECT IDENTIFIER ::= { 1 3 6 1 4 1 2312 100 1 1 }
alarmsAsObjects		OBJECT IDENTIFIER ::= { 1 3 6 1 4 1 2312 101 1 100 1 }
system		OBJECT IDENTIFIER ::= { 1 3 6 1 2 1 1 }
sleeAlarmsAsTraps		OBJECT IDENTIFIER ::= { 1 3 6 1 4 1 2312 101 1 100 2 0 }
jbossAsTraps		OBJECT IDENTIFIER ::= { 1 3 6 1 4 1 2312 100 1 2 0 }
jbossJmxNotificationAll		OBJECT IDENTIFIER ::= { 1 3 6 1 4 1 2312 101 1 100 2 }

activeThreadCount OBJECT-TYPE
	SYNTAX INTEGER
	ACCESS read-only
	STATUS current
	DESCRIPTION 
		"The amount of active threads the server is handling."
::= { jbossAsObjects 1 }

freeMemory OBJECT-TYPE
	SYNTAX OCTET STRING (SIZE(0..255))
	ACCESS read-only
	STATUS current
	DESCRIPTION 
		"The amount of free memory on the server."
::= { jbossAsObjects 2 }

maxMemory OBJECT-TYPE
	SYNTAX OCTET STRING (SIZE(0..255))
	ACCESS read-only
	STATUS current
	DESCRIPTION 
		"The maximum usable amount of memory on the server."
::= { jbossAsObjects 3 }

instantiationTime OBJECT-TYPE
	SYNTAX DisplayString
	ACCESS read-only
	STATUS current
	DESCRIPTION 
		"The start time of the SNMP agent."
::= { jbossAsObjects 4 }

trapCount OBJECT-TYPE
	SYNTAX DisplayString
	ACCESS read-only
	STATUS current
	DESCRIPTION 
		"The number of traps emitted by the agent."
::= { jbossAsObjects 5 }

bindAddress OBJECT-TYPE
	SYNTAX DisplayString
	ACCESS read-only
	STATUS current
	DESCRIPTION 
		"The address to which the agent is bound."
::= { jbossAsObjects 6 }

inUseConnectionCount OBJECT-TYPE
	SYNTAX OCTET STRING (SIZE(0..255))
	ACCESS read-only
	STATUS current
	DESCRIPTION 
		"The amount of connections currently in use."
::= { jbossAsObjects 7 }

maxConnectionsInUseCount OBJECT-TYPE
	SYNTAX OCTET STRING (SIZE(0..255))
	ACCESS read-only
	STATUS current
	DESCRIPTION 
		"The maximum possible amount of connections available for use."
::= { jbossAsObjects 8 }

commitCount OBJECT-TYPE
	SYNTAX OCTET STRING (SIZE(0..255))
	ACCESS read-only
	STATUS current
	DESCRIPTION 
		""
::= { jbossAsObjects 9 }

rollbackCount OBJECT-TYPE
	SYNTAX OCTET STRING (SIZE(0..255))
	ACCESS read-only
	STATUS current
	DESCRIPTION 
		""
::= { jbossAsObjects 10 }

transactionCount OBJECT-TYPE
	SYNTAX OCTET STRING (SIZE(0..255))
	ACCESS read-only
	STATUS current
	DESCRIPTION 
		""
::= { jbossAsObjects 11 }

sysDescr OBJECT-TYPE
	SYNTAX OCTET STRING (SIZE(0..255))
	ACCESS read-write
	STATUS current
	DESCRIPTION 
		"A description of this System."
::= { system 1 }

sysObjectId OBJECT-TYPE
	SYNTAX OCTET STRING (SIZE(0..255))
	ACCESS read-only
	STATUS current
	DESCRIPTION 
		"The OID Denoting this system."
::= { system 2 }

sysUpTime OBJECT-TYPE
	SYNTAX OCTET STRING (SIZE(0..255))
	ACCESS read-only
	STATUS current
	DESCRIPTION 
		"The time this system has been online."
::= { system 3 }

sysContact OBJECT-TYPE
	SYNTAX OCTET STRING (SIZE(0..255))
	ACCESS read-only
	STATUS current
	DESCRIPTION 
		"The person who is admin to this system."
::= { system 4 }

sysName OBJECT-TYPE
	SYNTAX OCTET STRING (SIZE(0..255))
	ACCESS read-only
	STATUS current
	DESCRIPTION 
		"The name this system is known by."
::= { system 5 }

sysLocation OBJECT-TYPE
	SYNTAX OCTET STRING (SIZE(0..255))
	ACCESS read-only
	STATUS current
	DESCRIPTION 
		"The physical location of this system."
::= { system 6 }

sysServices OBJECT-TYPE
	SYNTAX OCTET STRING (SIZE(0..255))
	ACCESS read-only
	STATUS current
	DESCRIPTION 
		"The services provided by this system."
::= { system 7 }

jbossJmxNotificationMessage OBJECT-TYPE
	SYNTAX DisplayString
	ACCESS not-accessible
	STATUS current
	DESCRIPTION 
		""
::= { jbossAsObjects 30 }

jbossJmxNotificationSequenceNumber OBJECT-TYPE
	SYNTAX DisplayString
	ACCESS not-accessible
	STATUS current
	DESCRIPTION 
		""
::= { jbossAsObjects 31 }

jbossJmxNotificationMessage OBJECT-TYPE
	SYNTAX DisplayString
	ACCESS not-accessible
	STATUS current
	DESCRIPTION 
		""
::= { jbossAsObjects 1000 }

jbossJmxNotificationAll OBJECT-TYPE
	SYNTAX DisplayString
	ACCESS not-accessible
	STATUS current
	DESCRIPTION 
		""
::= { jbossJmxNotificationAll 1 }

jbossAsHeartbeatNotification NOTIFICATION-TYPE
	OBJECTS {
		sysUpTime,
		trapCount,
		jbossJmxNotificationMessage,
		jbossJmxNotificationSequenceNumber
		}
	STATUS current
	DESCRIPTION 
		""
::= { jbossAsTraps 3 }

jbossAsColdstartNotification NOTIFICATION-TYPE
	OBJECTS {
		instantiationTime,
		trapCount
		}
	STATUS current
	DESCRIPTION 
		""
::= { jbossAsTraps 1 }

jbossAsClusterViewChangedNotification NOTIFICATION-TYPE
	OBJECTS {
		instantiationTime,
		trapCount,
		jbossJmxNotificationMessage
		}
	STATUS current
	DESCRIPTION 
		""
::= { jbossAsTraps 0 }

sleeAlarmsNotification NOTIFICATION-TYPE
	OBJECTS {
		jbossJmxNotificationAll
		}
	STATUS current
	DESCRIPTION 
		""
::= { sleeAlarmsAsTraps 0 }

alarmsTable OBJECT-TYPE
	SYNTAX	SEQUENCE OF AlarmsEntry
	MAX-ACCESS	not-accessible
	STATUS	current
	DESCRIPTION
		"List of Alarms objects"
::= { alarmsAsObjects 1 }

alarmsEntry OBJECT-TYPE
	SYNTAX	AlarmsEntry
	MAX-ACCESS	not-accessible
	STATUS	current
	DESCRIPTION
		""

		INDEX	{
		IMPLIED index
		}
::= { alarmsTable 1 }

AlarmsEntry ::= SEQUENCE {
	index	DisplayString,
	element	DisplayString
}

index OBJECT-TYPE
	SYNTAX DisplayString
	ACCESS not-accessible
	STATUS current
	DESCRIPTION 
		""
::= { alarmsEntry 1 }

element OBJECT-TYPE
	SYNTAX DisplayString
	ACCESS read-only
	STATUS current
	DESCRIPTION 
		""
::= { alarmsEntry 2 }


metricsTable OBJECT-TYPE
	SYNTAX	SEQUENCE OF MetricsEntry
	MAX-ACCESS	not-accessible
	STATUS	current
	DESCRIPTION
		"Table containing standard metrics for any webapp deployed on JBossAS"
::= { jbossAsObjects 12 }

metricsEntry OBJECT-TYPE
	SYNTAX	MetricsEntry
	MAX-ACCESS	not-accessible
	STATUS	current
	DESCRIPTION
		""

		INDEX	{
		IMPLIED metricsObjectName
		}
::= { metricsTable 1 }

MetricsEntry ::= SEQUENCE {
	metricsObjectName	DisplayString,
	metricsDistributable	INTEGER,
	metricsSessionCounter	INTEGER,
	metricsActiveSessions	INTEGER,
	metricsMaxActiveSessions	INTEGER,
	metricsSessionAverageAliveTime	INTEGER,
	metricsExpiredSessions	INTEGER,
	metricsRejectedSessions	INTEGER,
	metricsMaxInactiveInterval	INTEGER,
	metricsSessionMaxAliveTime	INTEGER
}

metricsObjectName OBJECT-TYPE
	SYNTAX DisplayString
	ACCESS not-accessible
	STATUS current
	DESCRIPTION 
		""
::= { metricsEntry 1 }

metricsDistributable OBJECT-TYPE
	SYNTAX INTEGER
	ACCESS read-only
	STATUS current
	DESCRIPTION 
		""
::= { metricsEntry 2 }

metricsSessionCounter OBJECT-TYPE
	SYNTAX INTEGER
	ACCESS read-only
	STATUS current
	DESCRIPTION 
		"The amount of sessions this web application has handled."
::= { metricsEntry 3 }

metricsActiveSessions OBJECT-TYPE
	SYNTAX INTEGER
	ACCESS read-only
	STATUS current
	DESCRIPTION 
		"The amount of currently active sessions this web application is handling."
::= { metricsEntry 4 }

metricsMaxActiveSessions OBJECT-TYPE
	SYNTAX INTEGER
	ACCESS read-write
	STATUS current
	DESCRIPTION 
		"The maximum amount of active sessions this web application can handle at once."
::= { metricsEntry 5 }

metricsSessionAverageAliveTime OBJECT-TYPE
	SYNTAX INTEGER
	ACCESS read-only
	STATUS current
	DESCRIPTION 
		"The average time a session is active on this web application."
::= { metricsEntry 6 }

metricsExpiredSessions OBJECT-TYPE
	SYNTAX INTEGER
	ACCESS read-only
	STATUS current
	DESCRIPTION 
		"The amount of expired sessions related to this web application."
::= { metricsEntry 7 }

metricsRejectedSessions OBJECT-TYPE
	SYNTAX INTEGER
	ACCESS read-only
	STATUS current
	DESCRIPTION 
		"The amount of rejected sessions related to this web application."
::= { metricsEntry 8 }

metricsMaxInactiveInterval OBJECT-TYPE
	SYNTAX INTEGER
	ACCESS read-only
	STATUS current
	DESCRIPTION 
		"The amount of time that must expire before a session is considered inactive."
::= { metricsEntry 9 }

metricsSessionMaxAliveTime OBJECT-TYPE
	SYNTAX INTEGER
	ACCESS read-only
	STATUS current
	DESCRIPTION 
		"The maximum amount of time a session can remain active."
::= { metricsEntry 10 }


END
